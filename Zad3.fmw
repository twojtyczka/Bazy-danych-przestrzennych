FME workspace Zad3.fmw

Parameters:
- DestDataset_POSTGIS_RASTER =
- SourceDataset_POSTGIS_RASTER_3 =
- SourceDataset_SHAPEFILE =

Readers:
- SHAPEFILE_1: SHAPEFILE from $(SourceDataset_SHAPEFILE)
- POSTGIS_RASTER_2: POSTGIS_RASTER from $(SourceDataset_POSTGIS_RASTER_3)

Writers:
- POSTGIS_RASTER_1: POSTGIS_RASTER to $(DestDataset_POSTGIS_RASTER)

scotland_and_wales_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> Tester
Tester
    BOOL_OP = OR
    COMPOSITE_TEST = 1
    TEST_CLAUSE = CASE_INSENSITIVE_TEST @Value(FILE_NAME) BEGINS_WITH SOUTH_WALES
    TEST_MODE = CASE_INSENSITIVE_TEST
    PASSED -> Aggregator
Aggregator
    ACCUM_ATTRS_NAME = Use Attributes From One Feature
    AGGREGATE_TYPE = Homogeneous Collection (If Possible)
    MODE = Geometry - Assemble One Level
    SEP = ,
    AGGREGATE -> Clipper [CLIPPEE]
    AGGREGATE -> FeatureReader [INITIATOR]
FeatureReader
    ATTRIBUTES = GEOTIFF,fme_basename
    ATTR_ACCUM_MODE = Only Use Result
    COMBINE_GEOM = Use Result
    DATASET = ""$(FME_MF_DIR_ENCODED)Studia\Semestr 5\Bazy danych przestrzennych\Zajecia9-10\ras250_gb\ras250_gb\data\HP.tif" "$(FME_MF_DIR_ENCODED)Studia\Semestr 5\Bazy danych przestrzennych\Zajecia9-10\ras250_gb\ras250_gb\data\HT.tif" "$(FME_MF_DIR_ENCODED)Studia\Semestr 5\Bazy danych przestrzennych\Zajecia9-10\ras250_gb\ras250_gb\data\HU.tif" "$(FME_MF_DIR_ENCODED)Studia\Semestr 5\Bazy danych przestrzennych\Zajecia9-10\ras250_gb\ras250_gb\data\HW.tif" "$(FME_MF_DIR_ENCODED)Studia\Semestr 5\Bazy danych przestrzennych\Zajecia9-10\ras250_gb\ras250_gb\data\HX.tif" "$(FME_MF_DIR_ENCODED)Studia\Semestr 5\Bazy danych przestrzennych\Zajecia9-10\ras250_gb\ras250_gb\data\HY.tif" "$(FME_MF_DIR_ENCODED)Studia\Semestr 5\Bazy danych przestrzennych\Zajecia9-10\ras250_gb\ras250_gb\data\HZ.tif" "$(FME_MF_DIR_ENCODED)Studia\Semestr 5\Bazy danych przestrzennych\Zajecia9-10\ras250_gb\ras250_gb\data\NA.tif" "$(FME_MF_DIR_ENCODED)Studia\Semestr 5\Bazy danych przestrzennych\Zajecia9-10\ras250_gb\ras250_gb\data\NB.tif" "$(FME_MF_DIR_ENCODED)Studia\Semestr 5\Bazy danych przestrzennych\Zajecia9-10\ras250_gb\ras250_gb\data\NC.tif" "$(FME_MF_DIR_ENCODED)Studia\Semestr 5\Bazy danych przestrzennych\Zajecia9-10\ras250_gb\ras250_gb\data\ND.tif" "$(FME_MF_DIR_ENCODED)Studia\Semestr 5\Bazy danych przestrzennych\Zajecia9-10\ras250_gb\ras250_gb\data\NF.tif" "$(FME_MF_DIR_ENCODED)Studia\Semestr 5\Bazy danych przestrzennych\Zajecia9-10\ras250_gb\ras250_gb\data\NG.tif" "$(FME_MF_DIR_ENCODED)Studia\Semestr 5\Bazy danych przestrzennych\Zajecia9-10\ras250_gb\ras250_gb\data\NH.tif" "$(FME_MF_DIR_ENCODED)Studia\Semestr 5\Bazy danych przestrzennych\Zajecia9-10\ras250_gb\ras250_gb\data\NJ.tif" "$(FME_MF_DIR_ENCODED)Studia\Semestr 5\Bazy danych przestrzennych\Zajecia9-10\ras250_gb\ras250_gb\data\NK.tif" "$(FME_MF_DIR_ENCODED)Studia\Semestr 5\Bazy danych przestrzennych\Zajecia9-10\ras250_gb\ras250_gb\data\NL.tif" "$(FME_MF_DIR_ENCODED)Studia\Semestr 5\Bazy danych przestrzennych\Zajecia9-10\ras250_gb\ras250_gb\data\NM.tif" "$(FME_MF_DIR_ENCODED)Studia\Semestr 5\Bazy danych przestrzennych\Zajecia9-10\ras250_gb\ras250_gb\data\NN.tif" "$(FME_MF_DIR_ENCODED)Studia\Semestr 5\Bazy danych przestrzennych\Zajecia9-10\ras250_gb\ras250_gb\data\NO.tif" "$(FME_MF_DIR_ENCODED)Studia\Semestr 5\Bazy danych przestrzennych\Zajecia9-10\ras250_gb\ras250_gb\data\NR.tif" "$(FME_MF_DIR_ENCODED)Studia\Semestr 5\Bazy danych przestrzennych\Zajecia9-10\ras250_gb\ras250_gb\data\NS.tif" "$(FME_MF_DIR_ENCODED)Studia\Semestr 5\Bazy danych przestrzennych\Zajecia9-10\ras250_gb\ras250_gb\data\NT.tif" "$(FME_MF_DIR_ENCODED)Studia\Semestr 5\Bazy danych przestrzennych\Zajecia9-10\ras250_gb\ras250_gb\data\NU.tif" "$(FME_MF_DIR_ENCODED)Studia\Semestr 5\Bazy danych przestrzennych\Zajecia9-10\ras250_gb\ras250_gb\data\NW.tif" "$(FME_MF_DIR_ENCODED)Studia\Semestr 5\Bazy danych przestrzennych\Zajecia9-10\ras250_gb\ras250_gb\data\NX.tif" "$(FME_MF_DIR_ENCODED)Studia\Semestr 5\Bazy danych przestrzennych\Zajecia9-10\ras250_gb\ras250_gb\data\NY.tif" "$(FME_MF_DIR_ENCODED)Studia\Semestr 5\Bazy danych przestrzennych\Zajecia9-10\ras250_gb\ras250_gb\data\NZ.tif" "$(FME_MF_DIR_ENCODED)Studia\Semestr 5\Bazy danych przestrzennych\Zajecia9-10\ras250_gb\ras250_gb\data\OV.tif" "$(FME_MF_DIR_ENCODED)Studia\Semestr 5\Bazy danych przestrzennych\Zajecia9-10\ras250_gb\ras250_gb\data\SC.tif" "$(FME_MF_DIR_ENCODED)Studia\Semestr 5\Bazy danych przestrzennych\Zajecia9-10\ras250_gb\ras250_gb\data\SD.tif" "$(FME_MF_DIR_ENCODED)Studia\Semestr 5\Bazy danych przestrzennych\Zajecia9-10\ras250_gb\ras250_gb\data\SE.tif" "$(FME_MF_DIR_ENCODED)Studia\Semestr 5\Bazy danych przestrzennych\Zajecia9-10\ras250_gb\ras250_gb\data\SH.tif" "$(FME_MF_DIR_ENCODED)Studia\Semestr 5\Bazy danych przestrzennych\Zajecia9-10\ras250_gb\ras250_gb\data\SJ.tif" "$(FME_MF_DIR_ENCODED)Studia\Semestr 5\Bazy danych przestrzennych\Zajecia9-10\ras250_gb\ras250_gb\data\SK.tif" "$(FME_MF_DIR_ENCODED)Studia\Semestr 5\Bazy danych przestrzennych\Zajecia9-10\ras250_gb\ras250_gb\data\SM.tif" "$(FME_MF_DIR_ENCODED)Studia\Semestr 5\Bazy danych przestrzennych\Zajecia9-10\ras250_gb\ras250_gb\data\SN.tif" "$(FME_MF_DIR_ENCODED)Studia\Semestr 5\Bazy danych przestrzennych\Zajecia9-10\ras250_gb\ras250_gb\data\SO.tif" "$(FME_MF_DIR_ENCODED)Studia\Semestr 5\Bazy danych przestrzennych\Zajecia9-10\ras250_gb\ras250_gb\data\SP.tif" "$(FME_MF_DIR_ENCODED)Studia\Semestr 5\Bazy danych przestrzennych\Zajecia9-10\ras250_gb\ras250_gb\data\SR.tif" "$(FME_MF_DIR_ENCODED)Studia\Semestr 5\Bazy danych przestrzennych\Zajecia9-10\ras250_gb\ras250_gb\data\SS.tif" "$(FME_MF_DIR_ENCODED)Studia\Semestr 5\Bazy danych przestrzennych\Zajecia9-10\ras250_gb\ras250_gb\data\ST.tif" "$(FME_MF_DIR_ENCODED)Studia\Semestr 5\Bazy danych przestrzennych\Zajecia9-10\ras250_gb\ras250_gb\data\SU.tif" "$(FME_MF_DIR_ENCODED)Studia\Semestr 5\Bazy danych przestrzennych\Zajecia9-10\ras250_gb\ras250_gb\data\SV.tif" "$(FME_MF_DIR_ENCODED)Studia\Semestr 5\Bazy danych przestrzennych\Zajecia9-10\ras250_gb\ras250_gb\data\SW.tif" "$(FME_MF_DIR_ENCODED)Studia\Semestr 5\Bazy danych przestrzennych\Zajecia9-10\ras250_gb\ras250_gb\data\SX.tif" "$(FME_MF_DIR_ENCODED)Studia\Semestr 5\Bazy danych przestrzennych\Zajecia9-10\ras250_gb\ras250_gb\data\SY.tif" "$(FME_MF_DIR_ENCODED)Studia\Semestr 5\Bazy danych przestrzennych\Zajecia9-10\ras250_gb\ras250_gb\data\SZ.tif" "$(FME_MF_DIR_ENCODED)Studia\Semestr 5\Bazy danych przestrzennych\Zajecia9-10\ras250_gb\ras250_gb\data\TA.tif" "$(FME_MF_DIR_ENCODED)Studia\Semestr 5\Bazy danych przestrzennych\Zajecia9-10\ras250_gb\ras250_gb\data\TF.tif" "$(FME_MF_DIR_ENCODED)Studia\Semestr 5\Bazy danych przestrzennych\Zajecia9-10\ras250_gb\ras250_gb\data\TG.tif" "$(FME_MF_DIR_ENCODED)Studia\Semestr 5\Bazy danych przestrzennych\Zajecia9-10\ras250_gb\ras250_gb\data\TL.tif" "$(FME_MF_DIR_ENCODED)Studia\Semestr 5\Bazy danych przestrzennych\Zajecia9-10\ras250_gb\ras250_gb\data\TM.tif" "$(FME_MF_DIR_ENCODED)Studia\Semestr 5\Bazy danych przestrzennych\Zajecia9-10\ras250_gb\ras250_gb\data\TQ.tif" "$(FME_MF_DIR_ENCODED)Studia\Semestr 5\Bazy danych przestrzennych\Zajecia9-10\ras250_gb\ras250_gb\data\TR.tif" "$(FME_MF_DIR_ENCODED)Studia\Semestr 5\Bazy danych przestrzennych\Zajecia9-10\ras250_gb\ras250_gb\data\TV.tif""
    FORMAT = GEOTIFF
    GEOTIFF_APPLY_GCPS = NO
    GEOTIFF_FEATURE_TYPE_NAME = FORMAT_NAME
    GEOTIFF_GEOTIFF_EXPOSE_FORMAT_ATTRS = fme_basename,char(50)
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = INTERSECTS
    OUTPUT_FEATURES_DISPLAY = Schema and Data Features
    GEOTIFF -> DuplicateFilter
    GEOTIFF -> Clipper_2 [CLIPPEE]
DuplicateFilter
    INPUT_ORDERED_CHOICE = No
    KEYATTR = fme_basename
    UNIQUE -> Clipper [CLIPPER]
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Clipper_2 [CLIPPER]
Clipper_2
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> RasterPaletteResolver
RasterPaletteResolver
    -> Exports (writer POSTGIS_RASTER_1)
Exports (writer POSTGIS_RASTER_1)
    attributes: _clipped char(3)
Exports (reader POSTGIS_RASTER_2)
    attributes: _clipped char(3)
